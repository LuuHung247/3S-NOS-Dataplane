module nos-iptables {
  namespace "urn:3snos:iptables";
  prefix snit;

  import ietf-inet-types {
    prefix inet;
  }

  organization "3S-NOS Secure Framework";
  description
    "YANG model for iptables FORWARD chain management on SONiC-VS.
     Maps 1-to-1 with iptables semantics. Used by Secure Framework
     to push rules via gNMI to LEAF switches. The nos-acl-bridge
     daemon on each LEAF subscribes ConfigDB and translates to iptables.";

  revision 2026-04-26 {
    description "Initial version — 3S-NOS Secure Framework";
  }

  container nos-iptables {
    description "Root container for 3S-NOS iptables rule management";

    list rule {
      key "rule-id";
      description "An iptables FORWARD rule managed by Secure Framework";

      leaf rule-id {
        type string {
          length "1..128";
          pattern '[a-zA-Z0-9_\-]+';
        }
        description "Unique rule identifier. Pattern: auto-block-{epoch_ms}-{hash}";
      }

      leaf chain {
        type enumeration {
          enum FORWARD { description "iptables FORWARD chain (default — inter-zone)"; }
          enum INPUT   { description "iptables INPUT chain"; }
          enum OUTPUT  { description "iptables OUTPUT chain"; }
        }
        default FORWARD;
        description "iptables chain to insert the rule into";
      }

      leaf src-prefix {
        type inet:ipv4-prefix;
        description "Source IP prefix (-s flag). Omit = match any source.";
      }

      leaf dst-prefix {
        type inet:ipv4-prefix;
        description "Destination IP prefix (-d flag). Omit = match any destination.";
      }

      leaf protocol {
        type enumeration {
          enum tcp  { description "TCP (-p tcp)"; }
          enum udp  { description "UDP (-p udp)"; }
          enum icmp { description "ICMP (-p icmp)"; }
          enum sctp { description "SCTP (-p sctp)"; }
          enum all  { description "Match all protocols (no -p flag)"; }
        }
        default all;
        description "IP protocol to match";
      }

      leaf src-port {
        when "../protocol = 'tcp' or ../protocol = 'udp' or ../protocol = 'sctp'";
        type uint16 {
          range "1..65535";
        }
        description "Source port (--sport). Only valid for tcp/udp/sctp.";
      }

      leaf dst-port {
        when "../protocol = 'tcp' or ../protocol = 'udp' or ../protocol = 'sctp'";
        type uint16 {
          range "1..65535";
        }
        description "Destination port (--dport). Only valid for tcp/udp/sctp.";
      }

      leaf action {
        type enumeration {
          enum DROP   { description "Drop packet silently (-j DROP)"; }
          enum ACCEPT { description "Accept packet (-j ACCEPT)"; }
          enum REJECT { description "Reject with ICMP (-j REJECT)"; }
        }
        mandatory true;
        description "iptables target (-j flag). Mandatory.";
      }

      leaf priority {
        type uint16 {
          range "1..9999";
        }
        default 1000;
        description
          "Insertion priority. Lower = higher priority (inserted earlier in chain).
           < 100  : iptables -I FORWARD 1  (top — IDS auto-block, overrides all)
           100-999: iptables -I FORWARD N  (after ESTABLISHED rule, before baseline ZT)
           >= 1000: iptables -A FORWARD    (append, does not disturb ZT baseline)
           Recommended: IDS auto-block = 50, manual SDNC rules = 1000.";
      }

      leaf source {
        type enumeration {
          enum sdnc     { description "Rule pushed by ONAP SDNC operator"; }
          enum ids-auto { description "Rule auto-generated by IDS alert"; }
          enum manual   { description "Manually inserted rule"; }
        }
        default sdnc;
        description "Origin of this rule — used for audit and TTL decisions";
      }

      leaf comment {
        type string {
          length "0..256";
        }
        description
          "Human-readable comment embedded in iptables rule
           (-m comment --comment 'nos:{rule-id}').
           Bridge auto-prefixes 'nos:{rule-id}' even if this leaf is absent.";
      }

      leaf ttl-seconds {
        type uint32 {
          range "0..86400";
        }
        default 0;
        description
          "Time-to-live in seconds. 0 = permanent (no auto-unblock).
           Agent-IDS sets this per severity: P1=900, P2=3600, P3=session-only.
           TTL tracking is handled by the caller (Agent-IDS), not by the bridge.";
      }
    }
  }
}
